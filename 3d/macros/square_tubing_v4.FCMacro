# -*- coding: utf-8 -*-

# Macro Begin: /home/pascalr/invention/macros/square_tubing_v4.FCMacro +++++++++++++++++++++++++++++++++++++++++++++++++
import FreeCAD
import PartDesign
import PartDesignGui
import Sketcher

App.activeDocument().Body.newObject('Sketcher::SketchObject','Sketch')
App.activeDocument().Sketch.Support = (App.activeDocument().XY_Plane, [''])
App.activeDocument().Sketch.MapMode = 'FlatFace'
App.ActiveDocument.recompute()
#Gui.activeDocument().setEdit('Sketch')
#Gui.activateWorkbench('SketcherWorkbench')
#ActiveSketch = App.ActiveDocument.getObject('Sketch')
#tv = Show.TempoVis(App.ActiveDocument)
#if ActiveSketch.ViewObject.HideDependent:
#  objs = tv.get_all_dependent(ActiveSketch)
#  objs = filter(lambda x: not x.TypeId.startswith("TechDraw::"), objs)
#  objs = filter(lambda x: not x.TypeId.startswith("Drawing::"), objs)
#  tv.hide(objs)
#if ActiveSketch.ViewObject.ShowSupport:
#  tv.show([ref[0] for ref in ActiveSketch.Support if not ref[0].isDerivedFrom("PartDesign::Plane")])
#if ActiveSketch.ViewObject.ShowLinks:
#  tv.show([ref[0] for ref in ActiveSketch.ExternalGeometry])
#tv.hide(ActiveSketch)
#ActiveSketch.ViewObject.TempoVis = tv
#del(tv)
#
#ActiveSketch = App.ActiveDocument.getObject('Sketch')
#if ActiveSketch.ViewObject.RestoreCamera:
#  ActiveSketch.ViewObject.TempoVis.saveCamera()
#
geoList = []
geoList.append(Part.LineSegment(App.Vector(-11.180576,10.992892,0),App.Vector(11.073330,10.992892,0)))
geoList.append(Part.LineSegment(App.Vector(11.073330,10.992892,0),App.Vector(11.073330,-11.475508,0)))
geoList.append(Part.LineSegment(App.Vector(11.073330,-11.475508,0),App.Vector(-11.180576,-11.475508,0)))
geoList.append(Part.LineSegment(App.Vector(-11.180576,-11.475508,0),App.Vector(-11.180576,10.992892,0)))
App.ActiveDocument.Sketch.addGeometry(geoList,False)
conList = []
conList.append(Sketcher.Constraint('Coincident',0,2,1,1))
conList.append(Sketcher.Constraint('Coincident',1,2,2,1))
conList.append(Sketcher.Constraint('Coincident',2,2,3,1))
conList.append(Sketcher.Constraint('Coincident',3,2,0,1))
conList.append(Sketcher.Constraint('Horizontal',0))
conList.append(Sketcher.Constraint('Horizontal',2))
conList.append(Sketcher.Constraint('Vertical',1))
conList.append(Sketcher.Constraint('Vertical',3))
App.ActiveDocument.Sketch.addConstraint(conList)

App.ActiveDocument.recompute()
App.ActiveDocument.Sketch.fillet(0,1,3.147178)
App.ActiveDocument.recompute()
App.ActiveDocument.Sketch.fillet(0,2,2.702099)
App.ActiveDocument.recompute()
App.ActiveDocument.Sketch.fillet(1,2,2.795377)
App.ActiveDocument.recompute()
App.ActiveDocument.Sketch.fillet(2,2,2.732433)
App.ActiveDocument.recompute()
App.ActiveDocument.Sketch.addConstraint(Sketcher.Constraint('Symmetric',4,3,6,3,-1,1)) 
App.ActiveDocument.recompute()
App.ActiveDocument.Sketch.addConstraint(Sketcher.Constraint('Equal',5,6)) 
App.ActiveDocument.Sketch.addConstraint(Sketcher.Constraint('Equal',6,7)) 
App.ActiveDocument.Sketch.addConstraint(Sketcher.Constraint('Equal',7,4)) 
App.ActiveDocument.recompute()
App.ActiveDocument.Sketch.addConstraint(Sketcher.Constraint('Diameter',5,6.552266)) 
App.ActiveDocument.Sketch.setDatum(16,App.Units.Quantity('1.587500 mm'))
App.ActiveDocument.recompute()
App.ActiveDocument.Sketch.addConstraint(Sketcher.Constraint('Equal',0,1)) 
App.ActiveDocument.recompute()
App.ActiveDocument.Sketch.addConstraint(Sketcher.Constraint('DistanceY',3,2,1,1,-0.000000)) 
App.ActiveDocument.recompute()
App.ActiveDocument.recompute()
App.ActiveDocument.Sketch.addConstraint(Sketcher.Constraint('DistanceX',3,2,1,1,17.086104)) 
App.ActiveDocument.Sketch.setDatum(18,App.Units.Quantity('12.700000 mm'))
App.ActiveDocument.recompute()
App.ActiveDocument.recompute()
#Gui.getDocument('Unnamed').resetEdit()
#ActiveSketch = App.ActiveDocument.getObject('Sketch')
#tv = ActiveSketch.ViewObject.TempoVis
#if tv:
#  tv.restore()
#ActiveSketch.ViewObject.TempoVis = None
#del(tv)
#
#Gui.activateWorkbench('PartDesignWorkbench')
App.getDocument('Unnamed').recompute()
App.activeDocument().Body.newObject("PartDesign::Pad","Pad")
App.activeDocument().Pad.Profile = App.activeDocument().Sketch
App.activeDocument().Pad.Length = 10.0
App.ActiveDocument.recompute()
#Gui.activeDocument().hide("Sketch")
App.ActiveDocument.recompute()
#Gui.ActiveDocument.Pad.ShapeColor=Gui.ActiveDocument.Body.ShapeColor
#Gui.ActiveDocument.Pad.LineColor=Gui.ActiveDocument.Body.LineColor
#Gui.ActiveDocument.Pad.PointColor=Gui.ActiveDocument.Body.PointColor
#Gui.ActiveDocument.Pad.Transparency=Gui.ActiveDocument.Body.Transparency
#Gui.ActiveDocument.Pad.DisplayMode=Gui.ActiveDocument.Body.DisplayMode
#Gui.activeDocument().setEdit('Pad', 0)
#Gui.Selection.clearSelection()
#Gui.activeDocument().hide("Sketch")
App.ActiveDocument.Pad.Length = 1219.200000
App.ActiveDocument.Pad.Length2 = 100.000000
App.ActiveDocument.Pad.Type = 0
App.ActiveDocument.Pad.UpToFace = None
App.ActiveDocument.Pad.Reversed = 0
App.ActiveDocument.Pad.Midplane = 0
App.ActiveDocument.Pad.Offset = 0.000000
App.ActiveDocument.recompute()
#Gui.activeDocument().resetEdit()
App.activeDocument().Body.newObject("PartDesign::Thickness","Thickness")
App.activeDocument().Thickness.Base = (App.ActiveDocument.Pad,["Face10"])
#Gui.Selection.clearSelection()
#Gui.activeDocument().hide("Pad")
App.ActiveDocument.recompute()
#Gui.ActiveDocument.Thickness.ShapeColor=Gui.ActiveDocument.Body.ShapeColor
#Gui.ActiveDocument.Thickness.LineColor=Gui.ActiveDocument.Body.LineColor
#Gui.ActiveDocument.Thickness.PointColor=Gui.ActiveDocument.Body.PointColor
#Gui.ActiveDocument.Thickness.Transparency=Gui.ActiveDocument.Body.Transparency
#Gui.ActiveDocument.Thickness.DisplayMode=Gui.ActiveDocument.Body.DisplayMode
#Gui.activeDocument().setEdit('Thickness', 0)
#Gui.Selection.clearSelection()
#Gui.activeDocument().resetEdit()
App.activeDocument().Body.newObject("PartDesign::Thickness","Thickness")
App.activeDocument().Thickness.Base = (App.ActiveDocument.Pad,["Face10"])
#Gui.Selection.clearSelection()
#Gui.activeDocument().hide("Pad")
App.ActiveDocument.recompute()
#Gui.ActiveDocument.Thickness.ShapeColor=Gui.ActiveDocument.Body.ShapeColor
#Gui.ActiveDocument.Thickness.LineColor=Gui.ActiveDocument.Body.LineColor
#Gui.ActiveDocument.Thickness.PointColor=Gui.ActiveDocument.Body.PointColor
#Gui.ActiveDocument.Thickness.Transparency=Gui.ActiveDocument.Body.Transparency
#Gui.ActiveDocument.Thickness.DisplayMode=Gui.ActiveDocument.Body.DisplayMode
#Gui.activeDocument().setEdit('Thickness', 0)
#Gui.Selection.clearSelection()
#Gui.activeDocument().resetEdit()
#Gui.activateWorkbench('SketcherWorkbench')
#ActiveSketch = App.ActiveDocument.getObject('Sketch')
#tv = Show.TempoVis(App.ActiveDocument)
#if ActiveSketch.ViewObject.HideDependent:
#  objs = tv.get_all_dependent(ActiveSketch)
#  objs = filter(lambda x: not x.TypeId.startswith("TechDraw::"), objs)
#  objs = filter(lambda x: not x.TypeId.startswith("Drawing::"), objs)
#  tv.hide(objs)
#if ActiveSketch.ViewObject.ShowSupport:
#  tv.show([ref[0] for ref in ActiveSketch.Support if not ref[0].isDerivedFrom("PartDesign::Plane")])
#if ActiveSketch.ViewObject.ShowLinks:
#  tv.show([ref[0] for ref in ActiveSketch.ExternalGeometry])
#tv.hide(ActiveSketch)
#ActiveSketch.ViewObject.TempoVis = tv
#del(tv)
#
#ActiveSketch = App.ActiveDocument.getObject('Sketch')
#if ActiveSketch.ViewObject.RestoreCamera:
#  ActiveSketch.ViewObject.TempoVis.saveCamera()
#
geoList = []
geoList.append(Part.LineSegment(App.Vector(-4.228946,3.364509,0),App.Vector(3.893278,3.364509,0)))
geoList.append(Part.LineSegment(App.Vector(3.893278,3.364509,0),App.Vector(3.893278,-4.274771,0)))
geoList.append(Part.LineSegment(App.Vector(3.893278,-4.274771,0),App.Vector(-4.228946,-4.274771,0)))
geoList.append(Part.LineSegment(App.Vector(-4.228946,-4.274771,0),App.Vector(-4.228946,3.364509,0)))
App.ActiveDocument.Sketch.addGeometry(geoList,False)
conList = []
conList.append(Sketcher.Constraint('Coincident',8,2,9,1))
conList.append(Sketcher.Constraint('Coincident',9,2,10,1))
conList.append(Sketcher.Constraint('Coincident',10,2,11,1))
conList.append(Sketcher.Constraint('Coincident',11,2,8,1))
conList.append(Sketcher.Constraint('Horizontal',8))
conList.append(Sketcher.Constraint('Horizontal',10))
conList.append(Sketcher.Constraint('Vertical',9))
conList.append(Sketcher.Constraint('Vertical',11))
App.ActiveDocument.Sketch.addConstraint(conList)

App.ActiveDocument.recompute()
App.ActiveDocument.Sketch.fillet(8,1,1.080357)
App.ActiveDocument.recompute()
App.ActiveDocument.Sketch.fillet(8,2,0.995870)
App.ActiveDocument.recompute()
App.ActiveDocument.Sketch.fillet(9,2,0.939520)
App.ActiveDocument.recompute()
App.ActiveDocument.Sketch.fillet(10,2,0.927572)
App.ActiveDocument.recompute()
#Gui.getDocument('Unnamed').resetEdit()
#ActiveSketch = App.ActiveDocument.getObject('Sketch')
#tv = ActiveSketch.ViewObject.TempoVis
#if tv:
#  tv.restore()
#ActiveSketch.ViewObject.TempoVis = None
#del(tv)
#
#Gui.activateWorkbench('PartDesignWorkbench')
App.getDocument('Unnamed').recompute()
# Macro End: /home/pascalr/invention/macros/square_tubing_v4.FCMacro +++++++++++++++++++++++++++++++++++++++++++++++++
