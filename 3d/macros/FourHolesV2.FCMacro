# -*- coding: utf-8 -*-

# Macro Begin: /home/pascalr/invention/macros/FourHolesV2.FCMacro +++++++++++++++++++++++++++++++++++++++++++++++++
import FreeCAD
import Sketcher

App.ActiveDocument.Sketch.addGeometry(Part.Circle(App.Vector(-18.971312,18.445320,0),App.Vector(0,0,1),6.256641),False)
App.ActiveDocument.Sketch.addGeometry(Part.Circle(App.Vector(17.459829,16.797682,0),App.Vector(0,0,1),5.818091),False)
App.ActiveDocument.Sketch.addGeometry(Part.Circle(App.Vector(-18.239029,-17.070465,0),App.Vector(0,0,1),7.579230),False)
App.ActiveDocument.Sketch.addGeometry(Part.Circle(App.Vector(11.784626,-14.690541,0),App.Vector(0,0,1),8.238197),False)
App.ActiveDocument.Sketch.addConstraint(Sketcher.Constraint('Horizontal',1,3,0,3)) 
App.ActiveDocument.Sketch.addConstraint(Sketcher.Constraint('Vertical',3,3,1,3)) 
App.ActiveDocument.Sketch.addConstraint(Sketcher.Constraint('Horizontal',3,3,2,3)) 
App.ActiveDocument.Sketch.addConstraint(Sketcher.Constraint('Vertical',2,3,0,3)) 
App.ActiveDocument.Sketch.addConstraint(Sketcher.Constraint('Equal',0,1)) 
App.ActiveDocument.Sketch.addConstraint(Sketcher.Constraint('Equal',1,2)) 
App.ActiveDocument.Sketch.addConstraint(Sketcher.Constraint('Equal',2,3)) 
App.ActiveDocument.Sketch.addConstraint(Sketcher.Constraint('Diameter',1,12.513282)) 
App.ActiveDocument.Sketch.setDatum(7,App.Units.Quantity('5.588000 mm'))
# Macro End: /home/pascalr/invention/macros/FourHolesV2.FCMacro +++++++++++++++++++++++++++++++++++++++++++++++++
