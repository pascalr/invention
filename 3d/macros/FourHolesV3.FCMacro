# -*- coding: utf-8 -*-

# Macro Begin: /home/pascalr/invention/macros/FourHolesV3.FCMacro +++++++++++++++++++++++++++++++++++++++++++++++++
import FreeCAD
import Sketcher

App.ActiveDocument.getInEdit().addGeometry(Part.Circle(App.Vector(-18.816412,9.394143,0),App.Vector(0,0,1),4.316333),False)
App.ActiveDocument.getInEdit().addGeometry(Part.Circle(App.Vector(23.921345,10.351853,0),App.Vector(0,0,1),4.134885),False)
App.ActiveDocument.getInEdit().addGeometry(Part.Circle(App.Vector(24.160770,-6.408051,0),App.Vector(0,0,1),4.682625),False)
App.ActiveDocument.getInEdit().addGeometry(Part.Circle(App.Vector(-21.090971,-6.767191,0),App.Vector(0,0,1),3.785673),False)
App.ActiveDocument.getInEdit().addConstraint(Sketcher.Constraint('Equal',0,1)) 
App.ActiveDocument.getInEdit().addConstraint(Sketcher.Constraint('Equal',1,2)) 
App.ActiveDocument.getInEdit().addConstraint(Sketcher.Constraint('Equal',2,3)) 
App.ActiveDocument.getInEdit().addConstraint(Sketcher.Constraint('Horizontal',0,3,1,3)) 
App.ActiveDocument.getInEdit().addConstraint(Sketcher.Constraint('Vertical',2,3,1,3)) 
App.ActiveDocument.getInEdit().addConstraint(Sketcher.Constraint('Horizontal',2,3,3,3)) 
App.ActiveDocument.getInEdit().addConstraint(Sketcher.Constraint('Vertical',3,3,0,3)) 
App.ActiveDocument.getInEdit().addConstraint(Sketcher.Constraint('Diameter',0,8.632666)) 
App.ActiveDocument.getInEdit().setDatum(7,App.Units.Quantity('5.334000 mm'))
# Macro End: /home/pascalr/invention/macros/FourHolesV3.FCMacro +++++++++++++++++++++++++++++++++++++++++++++++++
